# Based on macro by Damian Łoziński
# https://github.com/FreeCAD/FreeCAD-macros/blob/54df84d1de9a549e8291e68248cd8176833c98a1/ImportExport/Export2Slicer.FCMacro

__Title__ = "Export to Slicer"
__Author__ = "Damian Łoziński, Jennifer Wilcox"
__Comment__ = "Export selected objects to amf/stl files and open it in Slicer"
__Files__ = "PrusaSlicer.png"

import os
import subprocess
import tempfile
import Mesh
import MeshPart
import FreeCAD as app

MACRO_PARAMS_PATH = "User parameter:BaseApp/Preferences/Macros/Export2Slicer"
DEFAULT_SLICER_PATH = "/home/jwilcox/.local/bin/prusa-slicer"
DEFAUL_MESH_FORMAT = "stl"
DEFAULT_ANGULAR_DEFLECTION = 0.07

macro_params = app.ParamGet(MACRO_PARAMS_PATH)

slicer_path = macro_params.GetString("SlicerPath")
if not slicer_path:
    macro_params.SetString("SlicerPath", DEFAULT_SLICER_PATH)
    slicer_path = DEFAULT_SLICER_PATH

output_format = macro_params.GetString("OutputFormat")
if not output_format:
    macro_params.SetString("OutputFormat", DEFAUL_MESH_FORMAT)
    output_format = DEFAUL_MESH_FORMAT

angular_deflection = macro_params.GetFloat("AngularDeflection")
if not angular_deflection:
    macro_params.SetFloat("AngularDeflection", DEFAULT_ANGULAR_DEFLECTION)
    angular_deflection = DEFAULT_ANGULAR_DEFLECTION


def main():
    doc = app.activeDocument()
    if not doc:
        raise RuntimeError("No active document")

    objects_to_export = Gui.Selection.getSelection()

    try:
        # Create temporary doc to store meshes so that we don't affect current doc history
        tmp_doc = app.newDocument("meshes")
        meshes = []
        name = ""
        for o in objects_to_export:
            name += o.Label
            if o.TypeId == "Mesh::Feature":
                meshes.append(o)
            else:
                mesh = tmp_doc.addObject(
                    "Mesh::Feature", "{}_{}".format(doc.Label, o.Label)
                )
                mesh.Mesh = MeshPart.meshFromShape(
                    o.Shape,
                    LinearDeflection=0.1,
                    AngularDeflection=angular_deflection,
                    Relative=False,
                )
                meshes.append(mesh)

        if meshes:
            mesh_path = tempfile.mktemp(prefix=name + "-", suffix=".stl")
            Mesh.export(meshes, mesh_path)
        else:
            raise RuntimeError("No object selected")
    finally:
        app.closeDocument("meshes")

    subprocess.Popen((slicer_path, mesh_path))
    app.Console.PrintMessage("Export2Slicer: Objects exported: {}\n".format(mesh_path))


try:
    main()
except Exception as e:
    app.Console.PrintError("Export2Slicer error: {}\n".format(e))
